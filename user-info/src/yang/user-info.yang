module user-info {
  namespace "http://com/example/userinfo";
  prefix user-info;

  container person {
    leaf name { 
      type string;
      }
    leaf age {
      type uint32;
    }
    // The UInt16 ranges from 0 to 65535. The UInt32 ranges from 0 to 4294967295.
    leaf-list favorite-holiday-destinations { 
      type string;
    }
    leaf food-choice { 
      type enumeration {
        enum vegan;
        enum vegetarian;
        enum non-vegetarian;
      }
      default "vegetarian";
    }
}

}
